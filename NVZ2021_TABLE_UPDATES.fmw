FME workspace NVZ2021_TABLE_UPDATES.fmw

Parameters:
- DestDataset_ORACLE_SPATIAL = VSG   # Connection

Writers:
- ORACLE_SPATIAL_1: ORACLE_SPATIAL to $(DestDataset_ORACLE_SPATIAL) in EPSG:27700

Bookmark: Getting Date Last Updated by EA. Important to set the Run Order here.
Creator
    GEOMTYPE = Geometry Object
    NUM = 1
    CREATED -> HTTPCaller_7
HTTPCaller_7
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = xml
    TARGET_ATTR_ENCODING = auto-detect
    TARGET_URL = https://environment.data.gov.uk/arcgis/rest/services/EA/NitrateVulnerableZones2021Designations/FeatureServer/info/metadata
    TRANSFER_TIMEOUT_LENGTH = 90
    USE_COOKIES = No
    VERIFY_SSL_CERTIFICATES = Yes
    -> XMLFlattener
    <REJECTED> -> Terminator_4
XMLFlattener
    ATTRIBUTE_XML = xml
    EMBEDDED_EXPRESSIONS = CreaDate
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = CreaDate
    XML_SOURCE_TYPE = Attribute with XML document
    -> VariableSetter
VariableSetter
    SCOPE = Global
    VALUE = @Value(CreaDate)
    VARNAME = LAST_EDIT_DATE_EA
    -> SQLExecutor [INITIATOR]
Note: Terminate if network not connected
Terminator_4
    MESSAGE:
      Translation Terminated:
      Error Code: @Value(_http_status_code)
      Error Message: @Value(_error)
      Check network and try again.

Bookmark: Checking if SDM data is latest
SQLExecutor
    COMBINE_ATTRS = Result Attributes Only
    COMBINE_GEOM = Initiator Geometry Only
    DATASET = VSG
    EXPOSED_ATTRIBUTE_LIST = LAST_UPDATED_EA
    FORMAT = ORACLE_NONSPATIAL
    ORACLE_NONSPATIAL_CREATE_FEATURE_TABLES_FROM_DATA = Yes
    ORACLE_NONSPATIAL_NAMED_CONNECTION = VSG
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT:
      SELECT DISTINCT(TO_CHAR(DATE_UPDATED_BY_EA,'yyyyMMDD')) AS LAST_UPDATED_EA FROM VSG_RW.NVZ_2021
      WHERE TO_CHAR(DATE_UPDATED_BY_EA,'yyyyMMDD') = '@Value(CreaDate)'
    INITIATOR -> Tester_3
Tester_3
    BOOL_OP = OR
    COMPOSITE_TEST = 1
    TEST_CLAUSE = TEST @Value(_matched_records) = 0
    TEST_MODE = TEST
    PASSED -> HTTPCaller_2
    FAILED -> Terminator_3
Note: Terminate if SDM data is latest
Terminator_3
    MESSAGE:
      Translation Terminated:

      The dataset in SDM is latest. EA last edited NVZ_2021 data on @DateTimeFormat(@Value(CreaDate),%d-%m-%Y).

Bookmark: Calling the geoprocessing URL
Note: Calling submitJob task from EA AGOL
HTTPCaller_2
    ADDITIONAL_URL_PARAMETERS = f;json FullExtract;true MapService;EA/NitrateVulnerableZones2021Designations OutputFormat;GeoJSON RequestMode;SPATIAL env:outSR;27700 env:processSR;
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://environment.data.gov.uk/arcgis/rest/services/gp/DataDownload/GPServer/DataDownload/submitJob
    TRANSFER_TIMEOUT_LENGTH = 90
    USE_COOKIES = No
    VERIFY_SSL_CERTIFICATES = Yes
    -> JSONExtractor
Note: Extracting the jobId of the submitted job
JSONExtractor
    EXTRACT_QUERY_TABLE = job_id json["jobId"]
    JSON_DOCUMENT = @Value(_response_body)
    READ_FROM_FILE = NO
    EVALUATED -> Decelerator

Bookmark: Check the job status
Decelerator
    DECEL_TYPE = Per Feature Delay
    DELAY = 15
    -> HTTPCaller_3
HTTPCaller_3
    ADDITIONAL_URL_PARAMETERS = f;json
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://environment.data.gov.uk/arcgis/rest/services/gp/DataDownload/GPServer/DataDownload/jobs/@Value(job_id)
    TRANSFER_TIMEOUT_LENGTH = 90
    USE_COOKIES = No
    VERIFY_SSL_CERTIFICATES = Yes
    -> JSONExtractor_2
JSONExtractor_2
    EXTRACT_QUERY_TABLE = job_status json["jobStatus"]
    JSON_DOCUMENT = @Value(_response_body)
    READ_FROM_FILE = NO
    EVALUATED -> Tester

Bookmark: Using EA geoprocessing datadownload service to download the file. Much faster
Note: Testing if job succeeded
Tester
    BOOL_OP = OR
    COMPOSITE_TEST = 1
    TEST_CLAUSE = TEST @Value(job_status) = esriJobSucceeded
    TEST_MODE = TEST
    PASSED -> HTTPCaller_4
    FAILED -> Terminator
NVZ_2021 (writer ORACLE_SPATIAL_1)
    attributes: OBJECTID integer,PrimaryKey, NVZ_ID varchar2(20), UNIQUE_REF varchar2(20), NVZ_NAME varchar2(200), NVZ_TYPE varchar2(50), NVZ_STATUS varchar2(50), NVZ_2017 varchar2(100), NVZ_2021 varchar2(100), DATE_UPDATED_BY_EA date, DATED_UPDATED_DATABASE date
Note: Fetching the job status
Note: Allowing the gp task to complete before checking job status
Terminator
    MESSAGE:
      Translation Terminated:

      The job @Value(job_id) failed with status @Value(job_status).

      Please try again.

Bookmark: Fetching geojson URL
HTTPCaller_4
    ADDITIONAL_URL_PARAMETERS = f;json
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://environment.data.gov.uk/arcgis/rest/services/gp/DataDownload/GPServer/DataDownload/jobs/@Value(job_id)/results/OutputResult?f=json
    TRANSFER_TIMEOUT_LENGTH = 90
    USE_COOKIES = No
    VERIFY_SSL_CERTIFICATES = Yes
    -> JSONExtractor_3
Note: Getting the URL of the results.json
JSONExtractor_3
    EXTRACT_QUERY_TABLE = file_url json["value"]["url"]
    JSON_DOCUMENT = @Value(_response_body)
    READ_FROM_FILE = NO
    EVALUATED -> HTTPCaller

Bookmark: Extracting the zipped geojson URL
HTTPCaller
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = @Value(file_url)
    TRANSFER_TIMEOUT_LENGTH = 90
    USE_COOKIES = No
    VERIFY_SSL_CERTIFICATES = Yes
    -> JSONExtractor_4
JSONExtractor_4
    EXTRACT_QUERY_TABLE = geojson_url json["url"]
    JSON_DOCUMENT = @Value(_response_body)
    READ_FROM_FILE = NO
    EVALUATED -> FeatureReader [INITIATOR]

Bookmark: Reading GeoJSON and exposing attributes
FeatureReader
    ATTR_ACCUM_MODE = Only Use Result
    COMBINE_GEOM = Use Result
    DATASET = @Value(geojson_url)
    ESRIJSON_FLATTEN_MODE = ONE_LEVEL
    ESRIJSON_MAKE_DONUTS = No
    ESRIJSON_MAKE_PATHS = No
    ESRIJSON_SIMPLIFY_MULTIS = No
    ESRIJSON_USE_BASENAME_AS_DEFAULT_FEATURE_TYPE = No
    ESRIJSON_USE_SEARCH_ENVELOPE = NO
    FORMAT = ESRIJSON
    INTERACT = <No Spatial Filter>
    OUTPUT_FEATURES_DISPLAY = Schema and Data Features
    <OTHER> -> AttributeExposer_2
AttributeExposer_2
    ATTR_LIST = OBJECTID,unique_ref,nvz_id,nvz_name,nvz_status,nvz_type,nvz_2017,nvz_2021
    -> VariableRetriever_2
VariableRetriever_2
    SCOPE = Global
    VALUE_ATTR = DATE_UPDATED_BY_EA
    VARNAME = LAST_EDIT_DATE_EA
    -> AttributeManager_2
AttributeManager_2
    ATTR_TABLE:
      RENAME_SET_VALUE nvz_id > NVZ_ID
      RENAME_SET_VALUE unique_ref > UNIQUE_REF
      RENAME_SET_VALUE nvz_name > NVZ_NAME
      RENAME_SET_VALUE nvz_type > NVZ_TYPE
      SET_TO DATED_UPDATED_DATABASE = @DateTimeFormat(@DateTimeNow(),%Y%m%d)
      RENAME_SET_VALUE nvz_status > NVZ_STATUS
      RENAME_SET_VALUE nvz_2017 > NVZ_2017
      RENAME_SET_VALUE nvz_2021 > NVZ_2021
    -> NVZ_2021 (writer ORACLE_SPATIAL_1)
