FME workspace Generate_AGOL_Token.fmw

Parameters:
- Username = username   # ArcGIS Online Username
- Password =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

Note: Full query documentation can be found here / The REST API can be found here .

Bookmark: Authenticate with ArcGIS Online with generateToken
Note: Initiator
Creator
    GEOMTYPE = Geometry Object
    NUM = 1
    CREATED -> HTTPCaller
HTTPCaller
    ADDITIONAL_URL_PARAMETERS = client;referer expiration;60 f;json referer;https://arcgis.com
    CONNECTION_TIMEOUT_LENGTH = 60
    ERROR_ATTR = _error
    FOLLOW_REDIRECTS = FOLLOW_WITH_ORIGINAL_METHOD
    HTTP_METHOD = POST
    MULTIPARTS = username StringUpload SOURCE_EXPRESSION;$(Username);MIME_TYPE;application/x-www-form-urlencoded;FME_CONTROLLER_QUERY_FILE;transformers\dependencies\http\StringUpload.fme password StringUpload SOURCE_EXPRESSION;$(Password);MIME_TYPE;application/x-www-form-urlencoded;FME_CONTROLLER_QUERY_FILE;transformers\dependencies\http\StringUpload.fme
    REDIRECT_AUTH = ORIGINAL_DOMAIN_ONLY
    RESPONSE_HEADER_LIST_ATTR = _headers
    SAVE_FILE = Attribute
    STATUS_CODE_ATTR = _http_status_code
    TARGET_ATTR = arcgis_response
    TARGET_ATTR_ENCODING = auto-detect
    TARGET_URL = https://arcgis.com/sharing/rest/generateToken
    TRANSFER_TIMEOUT_LENGTH = 90
    UPLOAD_TYPE = Multipart / Form Data
    USE_COOKIES = No
    VERIFY_SSL_CERTIFICATES = Yes
    -> Tester
    <REJECTED> -> Terminator
Tester
    BOOL_OP = OR
    COMPOSITE_TEST = 1
    TEST_CLAUSE = TEST @Value(_http_status_code) = 200
    TEST_MODE = TEST
    PASSED -> JSONFragmenter
    FAILED -> Terminator_1
JSONFragmenter
    EXPLODE_FORMAT = JSON
    EXTRACT_ATTR = Yes
    JSON_ATTR = arcgis_response
    JSON_QUERY = json[*]
    NEW_ATTRIBUTES = code message details{0} details{1} details{2}
    READ_FROM_FILE = NO
    RECURSIVE = Yes
    REJECT_EMPTY_LISTS = YES
    FRAGMENTS -> TestFilter_2
TestFilter_2
    DEFAULT_VALUE = <UNFILTERED>
    TEST_LIST = "BOOL_OP,OR,COMPOSITE_TEST,""""""1"""""",TEST_CLAUSE,TEST @Value(json_index) = token",TokenPort,"BOOL_OP,OR,COMPOSITE_TEST,""""""1"""""",TEST_CLAUSE,TEST @Value(json_index) = error",Error
    TokenPort -> TestFilter_2_TokenPort
    Error -> Logger
TestFilter_2_TokenPort: Logger
    LOG_FEATURE = LOG_ONLY
    MAXCOORDS = 20
    MAXFEATS = 20
    MESSAGE:
      Token received and is
      @Value(arcgis_response)
    SEVERITY = INFO
Logger
    LOG_FEATURE = LOG_ONLY
    MAXCOORDS = 20
    MAXFEATS = 20
    MESSAGE:
      Failed:

      Error Code: @Value(code)
      Error Message: @Value(message)
      Error Details: @Value(details{0}), @Value(details{1}), @Value(details{2})
    SEVERITY = ERROR
Terminator_1
    MESSAGE:
      Translation Terminated Due to HTTPError

      HTTP Code: @Value(_http_status_code)
Terminator
    MESSAGE:
      Translation Terminated Due to HTTPError

      HTTP Code: @Value(_http_status_code)
      FME Rejection: @Value(fme_rejection_code)
      Error: @Value(_error)
