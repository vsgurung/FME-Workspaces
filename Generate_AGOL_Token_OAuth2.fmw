FME workspace Generate_AGOL_Token_OAuth2.fmw

Parameters:
- client_id = type your client id from AGOL
- client_secret =   # type the client secret from AGOL

Note: Generate token from AGOL using OAuth2 / 1. Register FME as an application using ArcGIS Developer Account. / 2. Get the client_id and client_secret / 3. Use the REST endpoint for OAuth2 to generate token. / 4. Keep the client_id and client_secret safe
Note: Full query documentation can be found here / The REST API can be found here .

Bookmark: Authenticate with ArcGIS Online with OAuth2 REST endpoint
Note: Initiator
Creator
    GEOMTYPE = Geometry Object
    NUM = 1
    CREATED -> HTTPCaller
HTTPCaller
    CONNECTION_TIMEOUT_LENGTH = 60
    ERROR_ATTR = _error
    FOLLOW_REDIRECTS = FOLLOW_WITH_ORIGINAL_METHOD
    HTTP_METHOD = POST
    MULTIPARTS = client_id StringUpload SOURCE_EXPRESSION;$(client_id);MIME_TYPE;application/x-www-form-urlencoded;FME_CONTROLLER_QUERY_FILE;transformers\dependencies\http\StringUpload.fme client_secret StringUpload SOURCE_EXPRESSION;$(client_secret);MIME_TYPE;application/x-www-form-urlencoded;FME_CONTROLLER_QUERY_FILE;transformers\dependencies\http\StringUpload.fme grant_type StringUpload SOURCE_EXPRESSION;client_credentials;MIME_TYPE;text/plain;FME_CONTROLLER_QUERY_FILE;transformers/dependencies/http/StringUpload.fme
    REDIRECT_AUTH = ORIGINAL_DOMAIN_ONLY
    RESPONSE_HEADER_LIST_ATTR = _headers
    SAVE_FILE = Attribute
    STATUS_CODE_ATTR = _http_status_code
    TARGET_ATTR = arcgis_response
    TARGET_ATTR_ENCODING = auto-detect
    TARGET_URL = https://www.arcgis.com/sharing/rest/oauth2/token
    TRANSFER_TIMEOUT_LENGTH = 90
    UPLOAD_TYPE = Multipart / Form Data
    USE_COOKIES = No
    VERIFY_SSL_CERTIFICATES = Yes
    -> Tester
    <REJECTED> -> Terminator
Tester
    BOOL_OP = OR
    COMPOSITE_TEST = 1
    TEST_CLAUSE = TEST @Value(_http_status_code) = 200
    TEST_MODE = TEST
    PASSED -> JSONFragmenter
    FAILED -> Terminator_1
JSONFragmenter
    EXPLODE_FORMAT = JSON
    EXTRACT_ATTR = Yes
    JSON_ATTR = arcgis_response
    JSON_QUERY = json[*]
    NEW_ATTRIBUTES = access_token error message error_description code
    READ_FROM_FILE = NO
    RECURSIVE = Yes
    REJECT_EMPTY_LISTS = YES
    FRAGMENTS -> TestFilter_2
TestFilter_2
    DEFAULT_VALUE = <UNFILTERED>
    TEST_LIST = "BOOL_OP,OR,COMPOSITE_TEST,""""""1"""""",TEST_CLAUSE,TEST @Value(json_index) = access_token",TokenPort,"BOOL_OP,OR,COMPOSITE_TEST,""""""1"""""",TEST_CLAUSE,TEST @Value(json_index) = error",Error
    TokenPort -> TestFilter_2_TokenPort
    Error -> Terminator_2
TestFilter_2_TokenPort: Logger
    LOG_FEATURE = LOG_ONLY
    MAXCOORDS = 20
    MAXFEATS = 20
    MESSAGE:
      Token received and is
      @Value(arcgis_response)
    SEVERITY = INFO
Terminator_2
    MESSAGE:
      Translation Terminated:

      Error Code: @Value(code)
      Error Message: @Value(message)
      Error Description: @Value(error_description)
Terminator_1
    MESSAGE:
      Translation Terminated Due to HTTPError

      HTTP Code: @Value(_http_status_code)
Terminator
    MESSAGE:
      Translation Terminated Due to HTTPError

      HTTP Code: @Value(_http_status_code)
      FME Rejection: @Value(fme_rejection_code)
      Error: @Value(_error)
