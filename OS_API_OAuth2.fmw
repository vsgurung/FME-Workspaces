FME workspace OS_API_OAuth2.fmw

Parameters:
- FME_USER_PARAM_PRIVATE_GRP =
- ProjectAPIKey =
- ProjectAPISecret =

Note: For using an particular API, ensure that it is added to the project. / If it is the OS APIs is not added to any project, both the access token or the key will not work
Creator
    GEOMTYPE = Geometry Object
    NUM = 1
    CREATED -> HTTPCaller
    CREATED -> HTTPCaller_3
Note: Content-Type header is important else the token is not recognised
HTTPCaller_2
    ADDITIONAL_URL_PARAMETERS = query;RG1 2NN format;json
    CONNECTION_TIMEOUT_LENGTH = 60
    CUSTOM_HEADERS = Authorization;@Value(authorisation_header) Content-Type;application/x-www-form-urlencoded
    ERROR_ATTR = _error
    FOLLOW_REDIRECTS = FOLLOW_WITH_GET
    HTTP_METHOD = GET
    MAX_HTTP_VERSION = HTTP_2
    MAX_TRANSFERS_IN_PROGRESS = 25
    REDIRECT_AUTH = ORIGINAL_DOMAIN_ONLY
    SAVE_FILE = Attribute
    STATUS_CODE_ATTR = _http_status_code
    TARGET_ATTR = _response_body
    TARGET_ATTR_ENCODING = auto-detect
    TARGET_URL = https://api.os.uk/search/names/v1/find
    TRANSFER_TIMEOUT_LENGTH = 90
    USE_COOKIES = No
    VERIFY_SSL_CERTIFICATES = Yes

Bookmark: Using OAuth
HTTPCaller
    AUTH_METHOD = Basic
    AUTH_PASSWORD = $(ProjectAPISecret)
    AUTH_USERNAME = $(ProjectAPIKey)
    CONNECTION_TIMEOUT_LENGTH = 60
    ERROR_ATTR = _error
    FOLLOW_REDIRECTS = FOLLOW_WITH_GET
    HTTP_METHOD = POST
    REDIRECT_AUTH = ORIGINAL_DOMAIN_ONLY
    SAVE_FILE = Attribute
    STATUS_CODE_ATTR = _http_status_code
    TARGET_ATTR = _response_body
    TARGET_ATTR_ENCODING = auto-detect
    TARGET_URL = https://api.os.uk/oauth2/token/v1
    TRANSFER_TIMEOUT_LENGTH = 90
    UPLOAD_BODY = grant_type=client_credentials
    UPLOAD_CONTENT_TYPE = URL Encoded (application/x-www-form-urlencoded)
    UPLOAD_TYPE = Specify Upload Body
    USE_COOKIES = No
    VERIFY_SSL_CERTIFICATES = Yes
    -> JSONFragmenter
    <REJECTED> -> Terminator
JSONFragmenter
    EXPLODE_FORMAT = JSON
    EXTRACT_ATTR = Yes
    JSON_ATTR = _response_body
    JSON_QUERY = json[*]
    READ_FROM_FILE = NO
    RECURSIVE = Yes
    REJECT_EMPTY_LISTS = YES
    FRAGMENTS -> TestFilter
TestFilter
    DEFAULT_VALUE = <UNFILTERED>
    TEST_LIST:
      "BOOL_OP,OR,COMPOSITE_TEST,""""""1"""""",TEST_CLAUSE,TEST @Value(json_index) = access_token",Token,"BOOL_OP,OR,COMPOSITE_TEST,""""""1 OR 2"""""",TEST_CLAUSE,CASE_INSENSITIVE_TEST @Value(json_index) CONTAINS error
      CASE_INSENSITIVE_TEST @Value(json_index) CONTAINS Error",Error
    Token -> AttributeCreator
AttributeCreator
    ATTR_TABLE = SET_TO authorisation_header = Bearer @Value(_response_body)
    -> HTTPCaller_2
Terminator
    MESSAGE:
      Translation Terminated:

      FME Error: @Value(_error)
      HTTP Status Code: @Value(_http_status_code)

Bookmark: Using key in HEADER
HTTPCaller_3
    ADDITIONAL_URL_PARAMETERS = query;RG6 5QB format;json maxresults;5
    CONNECTION_TIMEOUT_LENGTH = 60
    CUSTOM_HEADERS = key;$(ProjectAPIKey)
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://api.os.uk/search/names/v1/find?
    TRANSFER_TIMEOUT_LENGTH = 90
    USE_COOKIES = No
    VERIFY_SSL_CERTIFICATES = Yes
