FME workspace XCOM_FLA_TABLE_UPDATES.fmw

Parameters:
- DestDataset_ORACLE_SPATIAL_3 = VSG   # Connection
- srid:   # Python Script
      import requests
      import json
      
      url = 'https://services.arcgis.com/JJzESW51TqeY9uat/arcgis/rest/services/Special_Areas_of_Conservation_England/FeatureServer/0/?f=json'
      
      def fetch_srid(url):
          response = requests.get(url)
          response_data = json.loads(response.content)
          return response_data['extent']['spatialReference']['wkid']
      
      fetch_srid(url)
- xmin:   # Python Script
      import requests
      import json
      
      url = 'https://services2.arcgis.com/mHXjwgl3OARRqqD4/arcgis/rest/services/FellingLicenceApplicationsEngland/FeatureServer/0/?f=json'
      
      def fetch_xmin(url):
          response = requests.get(url)
          response_data = json.loads(response.content)
          return response_data['extent']['xmin']
      
      fetch_xmin(url)
- xmax:   # Python Script
      import requests
      import json
      
      url = 'https://services2.arcgis.com/mHXjwgl3OARRqqD4/arcgis/rest/services/FellingLicenceApplicationsEngland/FeatureServer/0/?f=json'
      
      def fetch_xmax(url):
          response = requests.get(url)
          response_data = json.loads(response.content)
          return response_data['extent']['xmax']
      
      fetch_xmax(url)
- ymin:   # Python Script
      import requests
      import json
      
      url = 'https://services2.arcgis.com/mHXjwgl3OARRqqD4/arcgis/rest/services/FellingLicenceApplicationsEngland/FeatureServer/0/?f=json'
      
      def fetch_ymin(url):
          response = requests.get(url)
          response_data = json.loads(response.content)
          return response_data['extent']['ymin']
      
      fetch_ymin(url)
- ymax:   # Python Script
      import requests
      import json
      
      url = 'https://services2.arcgis.com/mHXjwgl3OARRqqD4/arcgis/rest/services/FellingLicenceApplicationsEngland/FeatureServer/0/?f=json'
      
      def fetch_ymax(url):
          response = requests.get(url)
          response_data = json.loads(response.content)
          return response_data['extent']['ymax']
      
      fetch_ymax(url)

Writers:
- ORACLE_SPATIAL_1: ORACLE_SPATIAL to $(DestDataset_ORACLE_SPATIAL_3)

Bookmark: Checking Network Connectivity and Proceed
Creator
    GEOMTYPE = Geometry Object
    NUM = 1
    CREATED -> HTTPCaller
HTTPCaller
    ADDITIONAL_URL_PARAMETERS = f;json
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://services2.arcgis.com/mHXjwgl3OARRqqD4/arcgis/rest/services/FellingLicenceApplicationsEngland/FeatureServer/0/
    TRANSFER_TIMEOUT_LENGTH = 90
    USE_COOKIES = No
    VERIFY_SSL_CERTIFICATES = Yes
    -> Tester_3
    <REJECTED> -> Terminator_3
Tester_3
    BOOL_OP = OR
    COMPOSITE_TEST = 1
    TEST_CLAUSE = TEST @Value(_http_status_code) = 200
    TEST_MODE = TEST
    PASSED -> JSONExtractor_2
    FAILED -> Terminator_4
Terminator_4
    MESSAGE:
      Translation Terminated:
      Error Code: @Value(_http_status_code). Please check the error and try again.
Terminator_3
    MESSAGE:
      Translation Terminated:
      Error Code: @Value(_http_status_code)
      Error Message: @Value(_error).
      Please check the network connection.

Bookmark: Extracting Last Edit Date by FC
JSONExtractor_2
    EXTRACT_QUERY_TABLE = last_edit_date json["editingInfo"]["lastEditDate"]
    JSON_DOCUMENT = @Value(_response_body)
    READ_FROM_FILE = NO
    EVALUATED -> AttributeManager_8
AttributeManager_8
    ATTR_TABLE:
      REMOVE _creation_instance
      REMOVE _response_body
      REMOVE _http_status_code
      SET_TO last_edit_date = @div(@Value(last_edit_date), 1000)
    -> DateTimeConverter_3
DateTimeConverter_3
    DATETIME_ATTR = last_edit_date
    IN_FORMAT = %s$
    OUT_FORMAT = %Y%m%d
    PASSTHROUGH = NO
    REPAIR_INPUT = YES
    -> SQLExecutor_2 [INITIATOR]

Bookmark: Checking if SDM has latest FLA data
SQLExecutor_2
    COMBINE_ATTRS = Result Attributes Only
    COMBINE_GEOM = Initiator Geometry Only
    DATASET = VSG
    EXPOSED_ATTRIBUTE_LIST = LAST_UPDATED_FC
    FORMAT = ORACLE_NONSPATIAL
    ORACLE_NONSPATIAL_CREATE_FEATURE_TABLES_FROM_DATA = Yes
    ORACLE_NONSPATIAL_NAMED_CONNECTION = VSG
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT:
      SELECT DISTINCT(TO_CHAR(LAST_UPDATED_BY_FC,'yyyyMMDD')) FROM VSG_RW.FLA
      WHERE TO_CHAR(LAST_UPDATED_BY_FC,'yyyyMMDD') = '@Value(last_edit_date)'
    INITIATOR -> Tester_4
Tester_4
    BOOL_OP = OR
    COMPOSITE_TEST = 1
    TEST_CLAUSE = TEST @Value(_matched_records) = 0
    TEST_MODE = TEST
    PASSED -> VariableSetter_2
    FAILED -> Terminator_5

Bookmark: FLA
Terminator_5
    MESSAGE:
      Translation Terminated:

      The SAC dataset in SDM is the latest which was last edited on @DateTimeFormat(@Value(last_edit_date), %d-%m-%Y) by Forestry Commission.
Note: To be written into database table
VariableSetter_2
    SCOPE = Global
    VALUE = @Value(last_edit_date)
    VARNAME = FLA_last_edit_date
    -> FeatureReader [INITIATOR]

Bookmark: Writing FLA data to database table
FeatureReader
    ATTRIBUTES = Felling_Licence_Applications_England,"OBJECTID,Descriptr,Fell_ref,DateApp,Shape__Area,Shape__Length"
    ATTR_ACCUM_MODE = Only Use Result
    COMBINE_GEOM = Use Result
    DATASET = https://opendata.arcgis.com/datasets/f0fe491790df46f8bb01d54e6875ef63_0.geojson
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    Felling_Licence_Applications_England -> Reprojector_4
Reprojector_4
    DEST = OSGB-GPS-2015-OSTN15
    INTERPOLATION_TYPE_NAME = Nearest Neighbor
    RASTER_CELL_SIZE = Preserve Cells
    RASTER_TOLERANCE = 0.0
    SOURCE = Read from feature
    REPROJECTED -> VariableRetriever_2
VariableRetriever_2
    SCOPE = Global
    VALUE_ATTR = LAST_UPDATED_BY_FC
    VARNAME = FLA_last_edit_date
    -> AttributeManager_5
AttributeManager_5
    ATTR_TABLE:
      RENAME_SET_VALUE Descriptr > DESCRIPTION
      RENAME_SET_VALUE Fell_ref > FELL_REF
      RENAME_SET_VALUE DateApp > DATE_APP
      RENAME_SET_VALUE Shape__Area > GEOM_AREA
      REMOVE Shape__Length
      SET_TO DATE_UPDATED_DATABASE = @DateTimeFormat(@DateTimeNow(),%Y%m%d)
    -> FLA (writer ORACLE_SPATIAL_1)
FLA (writer ORACLE_SPATIAL_1)
    attributes: OBJECTID integer,PrimaryKey, DESCRIPTION varchar2(100), FELL_REF varchar2(20), DATE_APP varchar2(25), GEOM_AREA float, LAST_UPDATED_BY_FC date, DATE_UPDATED_DATABASE date
