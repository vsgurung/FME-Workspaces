FME workspace SpatialIndexCreator.fmw

Parameters:
- SourceDataset_MSSQL_SPATIAL = OS_SampleData   # SQL Server Connection

Readers:
- MSSQL_SPATIAL_1: MSSQL_SPATIAL from $(SourceDataset_MSSQL_SPATIAL)

dbo.OS_ABPLUS_SAMPLE (reader MSSQL_SPATIAL_1)
    attributes: OBJECTID integer, UPRN varchar(200), CLASS varchar(200), CUSTODIAN_CODE varchar(200), DEPT_NAME varchar(200), LEGAL_NAME varchar(200), SUB_BLDG_NAME varchar(200), BLDG_NAME varchar(200), BLDG_NUMBER integer, SAO_START_NO integer, SAO_START_SFX varchar(200), SAO_END_NO integer, SAO_END_SFX varchar(200), SAO_TEXT varchar(200), PAO_START_NO integer, PAO_START_SFX varchar(200), PAO_END_NO integer, PAO_END_SFX varchar(200), PAO_TEXT varchar(200), USRN varchar(200), STREET_NAME varchar(200), TOWN_NAME varchar(200), POSTCODE varchar(200), EASTING numeric(10,10), NORTHING numeric(10,10), LATITUDE numeric(20,10), LONGITUDE numeric(20,10), FULL_ADDRESS varchar(200)
    -> BoundingBoxAccumulator
BoundingBoxAccumulator
    TOPFER_INDEX = No
    ACCUM_ATTRS_NAME = Drop Incoming Attributes
    BOUNDING_BOX -> BoundsExtractor
BoundsExtractor
    YMIN = _ymin
    YMAX = _ymax
    ZMAX = _zmax
    ZMIN = _zmin
    XMIN = _xmin
    XMAX = _xmax
    -> SQLExecutor [INITIATOR]
SQLExecutor
    FORMAT = MSSQL_SPATIAL
    MSSQL_SPATIAL_QUERY_FEATURE_TYPES_FOR_MERGE_FILTERS = Yes
    DATASET = OS_SampleData
    MSSQL_SPATIAL_NAMED_CONNECTION = OS_SampleData
    COMBINE_ATTRS = Result Attributes Only
    COMBINE_GEOM = Initiator Geometry Only
    MSSQL_SPATIAL_COMMAND_TIMEOUT = 30
    SQL_STATEMENT:
      IF EXISTS(SELECT * FROM sys.indexes WHERE name='SI_OS_ABPLUS_SAMPLE' AND object_id=OBJECT_ID('dbo.[OS_ABPLUS_SAMPLE]'))
          BEGIN
          CREATE SPATIAL INDEX SI_OS_ABPLUS_SAMPLE ON dbo.[OS_ABPLUS_SAMPLE](GEOM)
          USING GEOMETRY_AUTO_GRID
          WITH (
              BOUNDING_BOX=(@Value(_xmin), @Value(_ymin),@Value(_xmax),@Value(_ymax)),
              CELLS_PER_OBJECT=16,
              DROP_EXISTING=ON
              )
          END
      ELSE
          CREATE SPATIAL INDEX SI_OS_ABPLUS_SAMPLE ON dbo.[OS_ABPLUS_SAMPLE](GEOM)
          USING GEOMETRY_AUTO_GRID
          WITH (
              BOUNDING_BOX=(@Value(_xmin), @Value(_ymin),@Value(_xmax),@Value(_ymax)),
              CELLS_PER_OBJECT=16
              )
