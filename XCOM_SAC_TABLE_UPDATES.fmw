FME workspace XCOM_SAC_TABLE_UPDATES.fmw

Parameters:
- DestDataset_ORACLE_SPATIAL = VSG   # Connection
- srid:   # Python Script
      import requests
      import json
      
      url = 'https://services.arcgis.com/JJzESW51TqeY9uat/arcgis/rest/services/Special_Areas_of_Conservation_England/FeatureServer/0/?f=json'
      
      def fetch_srid(url):
          response = requests.get(url)
          response_data = json.loads(response.content)
          return response_data['extent']['spatialReference']['wkid']
      
      fetch_srid(url)
- xmin:   # Python Script
      import requests
      import json
      
      url = 'https://services.arcgis.com/JJzESW51TqeY9uat/arcgis/rest/services/Special_Areas_of_Conservation_England/FeatureServer/0/?f=json'
      
      def fetch_xmin(url):
          response = requests.get(url)
          response_data = json.loads(response.content)
          return response_data['extent']['xmin']
      
      fetch_xmin(url)
- xmax:   # Python Script
      import requests
      import json
      
      url = 'https://services.arcgis.com/JJzESW51TqeY9uat/arcgis/rest/services/Special_Areas_of_Conservation_England/FeatureServer/0/?f=json'
      
      def fetch_xmax(url):
          response = requests.get(url)
          response_data = json.loads(response.content)
          return response_data['extent']['xmax']
      
      fetch_xmax(url)
- ymin:   # Python Script
      import requests
      import json
      
      url = 'https://services.arcgis.com/JJzESW51TqeY9uat/arcgis/rest/services/Special_Areas_of_Conservation_England/FeatureServer/0/?f=json'
      
      def fetch_ymin(url):
          response = requests.get(url)
          response_data = json.loads(response.content)
          return response_data['extent']['ymin']
      
      fetch_ymin(url)
- ymax:   # Python Script
      import requests
      import json
      
      url = 'https://services.arcgis.com/JJzESW51TqeY9uat/arcgis/rest/services/Special_Areas_of_Conservation_England/FeatureServer/0/?f=json'
      
      def fetch_ymax(url):
          response = requests.get(url)
          response_data = json.loads(response.content)
          return response_data['extent']['ymax']
      
      fetch_ymax(url)

Writers:
- ORACLE_SPATIAL_1: ORACLE_SPATIAL to $(DestDataset_ORACLE_SPATIAL)

Bookmark: Checking Network Connectivity and Proceed
Creator_3
    GEOMTYPE = Geometry Object
    NUM = 1
    CREATED -> HTTPCaller_3
HTTPCaller_3
    ADDITIONAL_URL_PARAMETERS = f;json
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://services.arcgis.com/JJzESW51TqeY9uat/arcgis/rest/services/Special_Areas_of_Conservation_England/FeatureServer/0/
    TRANSFER_TIMEOUT_LENGTH = 90
    USE_COOKIES = No
    VERIFY_SSL_CERTIFICATES = Yes
    -> Tester_3
    <REJECTED> -> Terminator_2
Tester_3
    BOOL_OP = OR
    COMPOSITE_TEST = 1
    TEST_CLAUSE = TEST @Value(_http_status_code) = 200
    TEST_MODE = TEST
    PASSED -> JSONExtractor_2
    FAILED -> Terminator_3
Terminator_3
    MESSAGE:
      Translation Terminated:
      The returned status_code is @Value(_http_status_code). Please check the reason.
Terminator_2
    MESSAGE:
      Translation Terminated:
      Error Code: @Value(_http_status_code).
      Error Message: @Value(_error).
      Please check network connection

Bookmark: Extracting Last Edit Date
JSONExtractor_2
    EXTRACT_QUERY_TABLE = last_edit_date json["editingInfo"]["lastEditDate"] xmin json["extent"]["xmin"] xmax json["extent"]["xmax"] ymin json["extent"]["ymin"] ymax json["extent"]["ymax"]
    JSON_DOCUMENT = @Value(_response_body)
    READ_FROM_FILE = NO
    EVALUATED -> AttributeManager_8
AttributeManager_8
    ATTR_TABLE:
      REMOVE _creation_instance
      REMOVE _response_body
      REMOVE _http_status_code
      SET_TO last_edit_date = @div(@Value(last_edit_date), 1000)
      SET_TO xmin = @Value(xmin)
      SET_TO xmax = @Value(xmax)
      SET_TO ymin = @Value(ymin)
      SET_TO ymax = @Value(ymax)
    -> DateTimeConverter_3
DateTimeConverter_3
    DATETIME_ATTR = last_edit_date
    IN_FORMAT = %s$
    OUT_FORMAT = %Y%m%d
    PASSTHROUGH = NO
    REPAIR_INPUT = YES
    -> SQLExecutor_2 [INITIATOR]

Bookmark: Checking if own dataset is up-to-date as per NE record
Note: Checking if database data updated since last updated by NE
SQLExecutor_2
    COMBINE_ATTRS = Result Attributes Only
    COMBINE_GEOM = Initiator Geometry Only
    DATASET = VSG
    EXPOSED_ATTRIBUTE_LIST = LAST_UPDATED_NE
    FORMAT = ORACLE_NONSPATIAL
    ORACLE_NONSPATIAL_CREATE_FEATURE_TABLES_FROM_DATA = Yes
    ORACLE_NONSPATIAL_NAMED_CONNECTION = VSG
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT:
      SELECT DISTINCT(TO_CHAR(LAST_UPDATED_BY_NE,'yyyyMMDD')) AS LAST_UPDATED_NE FROM VSG_RW.SAC
      WHERE TO_CHAR(LAST_UPDATED_BY_NE,'yyyyMMDD') = '@Value(last_edit_date)'
    INITIATOR -> Tester_4
Tester_4
    BOOL_OP = OR
    COMPOSITE_TEST = 1
    TEST_CLAUSE = TEST @Value(_matched_records) = 0
    TEST_MODE = TEST
    PASSED -> VariableSetter_2
    FAILED -> Terminator_4

Bookmark: Running SAC Update
Terminator_4
    MESSAGE:
      Translation Terminated:

      The SAC dataset in SDM is the latest which was last edited on @DateTimeFormat(@Value(last_edit_date), %d-%m-%Y) by NE.
Note: To be written into database table
VariableSetter_2
    SCOPE = Global
    VALUE = @Value(last_edit_date)
    VARNAME = SAC_last_edit_date
    -> FeatureReader [INITIATOR]

Bookmark: Reading JSON and Writing into Database
FeatureReader
    ATTRIBUTES = Special_Areas_of_Conservation__England____Natural_England,"OBJECTID,SAC_NAME,SAC_CODE,SAC_AREA,GRID_REF,EASTING,NORTHING,LATITUDE,LONGITUDE,NAME,STATUS,ID,FILE_,AREA,EASTING0,NORTHING0,GIS_DATE,VERSION,SHAPE_Length,SHAPE_Area"
    ATTR_ACCUM_MODE = Only Use Result
    COMBINE_GEOM = Use Result
    DATASET = https://opendata.arcgis.com/datasets/e4142658906c498fa37f0a20d3fdfcff_0.geojson
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    Special_Areas_of_Conservation__England____Natural_England -> Reprojector_2
Reprojector_2
    DEST = OSGB-GPS-2015-OSTN15
    INTERPOLATION_TYPE_NAME = Nearest Neighbor
    RASTER_CELL_SIZE = Preserve Cells
    RASTER_TOLERANCE = 0.0
    SOURCE = Read from feature
    REPROJECTED -> VariableRetriever_2
VariableRetriever_2
    SCOPE = Global
    VALUE_ATTR = LAST_UPDATED_BY_NE
    VARNAME = SAC_last_edit_date
    -> AttributeManager_2
AttributeManager_2
    ATTR_TABLE:
      REMOVE AREA
      REMOVE EASTING0
      REMOVE NORTHING0
      REMOVE VERSION
      REMOVE SHAPE_Length
      REMOVE SHAPE_Area
      REMOVE SAC_AREA
      REMOVE GRID_REF
      REMOVE NAME
      REMOVE ID
      REMOVE FILE_
      SET_TO DATE_UPDATED_DATABASE = @DateTimeFormat(@DateTimeNow(),%Y%m%d)
    -> SAC (writer ORACLE_SPATIAL_1)
SAC (writer ORACLE_SPATIAL_1)
    attributes: OBJECTID integer,PrimaryKey, SAC_NAME varchar2(200), SAC_CODE varchar2(20), STATUS varchar2(20), EASTING float, NORTHING float, LATITUDE varchar2(20), LONGITUDE varchar2(20), GIS_DATE date, LAST_UPDATED_BY_NE date, DATE_UPDATED_DATABASE date
