FME workspace XCOM_SSSI_TABLE_UPDATES.fmw

Parameters:
- DestDataset_ORACLE_SPATIAL = VSG   # Connection
- srid:   # Python Script
      import requests
      import json
      
      url = 'https://services.arcgis.com/JJzESW51TqeY9uat/arcgis/rest/services/SSSI_England/FeatureServer/0/?f=json'
      
      def fetch_srid(url):
          response = requests.get(url)
          response_data = json.loads(response.content)
          return response_data['extent']['spatialReference']['wkid']
      
      fetch_srid(url)
- xmin:   # Python Script
      import requests
      import json
      
      url = 'https://services.arcgis.com/JJzESW51TqeY9uat/arcgis/rest/services/SSSI_England/FeatureServer/0/?f=json'
      
      def fetch_xmin(url):
          response = requests.get(url)
          response_data = json.loads(response.content)
          return response_data['extent']['xmin']
      
      fetch_xmin(url)
- xmax:   # Python Script
      import requests
      import json
      
      url = 'https://services.arcgis.com/JJzESW51TqeY9uat/arcgis/rest/services/SSSI_England/FeatureServer/0/?f=json'
      
      def fetch_xmax(url):
          response = requests.get(url)
          response_data = json.loads(response.content)
          return response_data['extent']['xmax']
      
      fetch_xmax(url)
- ymin:   # Python Script
      import requests
      import json
      
      url = 'https://services.arcgis.com/JJzESW51TqeY9uat/arcgis/rest/services/SSSI_England/FeatureServer/0/?f=json'
      
      def fetch_ymin(url):
          response = requests.get(url)
          response_data = json.loads(response.content)
          return response_data['extent']['ymin']
      
      fetch_ymin(url)
- ymax:   # Python Script
      import requests
      import json
      
      url = 'https://services.arcgis.com/JJzESW51TqeY9uat/arcgis/rest/services/SSSI_England/FeatureServer/0/?f=json'
      
      def fetch_ymax(url):
          response = requests.get(url)
          response_data = json.loads(response.content)
          return response_data['extent']['ymax']
      
      fetch_ymax(url)

Writers:
- ORACLE_SPATIAL_1: ORACLE_SPATIAL to $(DestDataset_ORACLE_SPATIAL)

Note: This FME workbench downloads the latest SSSI data using REST API provided by NE. / a. The workbench has 5 Private Parameters, populated by Python script. The value of these private paramaeters are passed during creation of Oracle table.

Bookmark: Testing Network Connection
Creator_2
    GEOMTYPE = Geometry Object
    NUM = 1
    CREATED -> HTTPCaller_2
HTTPCaller_2
    ADDITIONAL_URL_PARAMETERS = f;json
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://services.arcgis.com/JJzESW51TqeY9uat/arcgis/rest/services/SSSI_England/FeatureServer/0/
    TRANSFER_TIMEOUT_LENGTH = 90
    USE_COOKIES = No
    VERIFY_SSL_CERTIFICATES = Yes
    -> Tester
    <REJECTED> -> Terminator_3
Tester
    BOOL_OP = OR
    COMPOSITE_TEST = 1
    TEST_CLAUSE = TEST @Value(_http_status_code) = 200
    TEST_MODE = TEST
    PASSED -> JSONExtractor
    FAILED -> Terminator
Terminator
    MESSAGE:
      Translation Terminated:
      The returned status_code is @Value(_http_status_code). Please check the reason.
Terminator_3
    MESSAGE:
      Translation Terminated:
      Error Code: @Value(_http_status_code).
      Error Message: @Value(_error).
      Please check network connection

Bookmark: Find the last edit date by NE
JSONExtractor
    EXTRACT_QUERY_TABLE = last_edit_date json["editingInfo"]["lastEditDate"]
    JSON_DOCUMENT = @Value(_response_body)
    READ_FROM_FILE = NO
    EVALUATED -> AttributeManager_7
AttributeManager_7
    ATTR_TABLE:
      REMOVE _creation_instance
      REMOVE _response_body
      REMOVE _http_status_code
      SET_TO last_edit_date = @div(@Value(last_edit_date), 1000)
    -> DateTimeConverter_2
DateTimeConverter_2
    DATETIME_ATTR = last_edit_date
    IN_FORMAT = %s$
    OUT_FORMAT = %Y%m%d
    PASSTHROUGH = NO
    REPAIR_INPUT = YES
    -> SQLExecutor [INITIATOR]

Bookmark: Checking the network status and the date data was last updated by NE and control the flow of workspace accordingly.
Note: Checking if database data updated since last updated by NE
SQLExecutor
    COMBINE_ATTRS = Result Attributes Only
    COMBINE_GEOM = Initiator Geometry Only
    DATASET = VSG
    EXPOSED_ATTRIBUTE_LIST = LAST_UPDATED_NE
    FORMAT = ORACLE_NONSPATIAL
    ORACLE_NONSPATIAL_CREATE_FEATURE_TABLES_FROM_DATA = Yes
    ORACLE_NONSPATIAL_NAMED_CONNECTION = VSG
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    SQL_STATEMENT:
      SELECT DISTINCT(TO_CHAR(LAST_UPDATED_BY_NE,'yyyyMMDD')) AS LAST_UPDATED_NE FROM VSG_RW.SSSI
      WHERE TO_CHAR(LAST_UPDATED_BY_NE,'yyyyMMDD') = '@Value(last_edit_date)'
    INITIATOR -> Tester_2

Bookmark: Testing Again for Matched Records to Terminate or Continute
Tester_2
    BOOL_OP = OR
    COMPOSITE_TEST = 1
    TEST_CLAUSE = TEST @Value(_matched_records) = 0
    TEST_MODE = TEST
    PASSED -> VariableSetter
    FAILED -> Terminator_2
Terminator_2
    MESSAGE:
      Translation Terminated:

      The SSSI dataset in SDM is the latest which was last edited on @DateTimeFormat(@Value(last_edit_date), %d-%m-%Y) by NE.
VariableSetter
    SCOPE = Global
    VALUE = @Value(last_edit_date)
    VARNAME = SSSI_last_edit_date
    -> FeatureReader [INITIATOR]

Bookmark: Write data into SSSI table if all OK
Note: Reading GeoJSON file directly from URL
FeatureReader
    ATTRIBUTES = Sites_of_Special_Scientific_Interest__England____Natural_England,"OBJECTID,SSSI_NAME,SSSI_AREA,EASTING,NORTHING,LATITUDE,LONGITUDE,REFERENCE,STATUS,GID,ENSISID,GIS_FILE,AREA,EASTING0,NORTHING0,GIS_DATE,VERSION,SHAPE_Length,SHAPE_Area"
    ATTR_ACCUM_MODE = Only Use Result
    COMBINE_GEOM = Use Result
    DATASET = https://opendata.arcgis.com/datasets/f10cbb4425154bfda349ccf493487a80_0.geojson
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    Sites_of_Special_Scientific_Interest__England____Natural_England -> Reprojector
Reprojector
    DEST = EPSG:27700
    INTERPOLATION_TYPE_NAME = Nearest Neighbor
    RASTER_CELL_SIZE = Preserve Cells
    RASTER_TOLERANCE = 0.0
    SOURCE = Read from feature
    REPROJECTED -> VariableRetriever
VariableRetriever
    SCOPE = Global
    VALUE_ATTR = LAST_UPDATED_BY_NE
    VARNAME = SSSI_last_edit_date
    -> AttributeManager
AttributeManager
    ATTR_TABLE:
      REMOVE GIS_FILE
      REMOVE AREA
      REMOVE EASTING0
      REMOVE NORTHING0
      REMOVE VERSION
      REMOVE SHAPE_Length
      REMOVE SHAPE_Area
      SET_TO DATE_UPDATED_DATABASE = @DateTimeFormat(@DateTimeNow(),%Y%m%d)
      SET_TO
    -> SSSI (writer ORACLE_SPATIAL_1)
SSSI (writer ORACLE_SPATIAL_1)
    attributes: OBJECTID integer,PrimaryKey, SSSI_NAME varchar2(20), SSSI_AREA float, EASTING float, NORTHING float, LATITUDE varchar2(20), LONGITUDE varchar2(20), REFERENCE varchar2(20), STATUS varchar2(20), GID float, ENSISID float, GIS_DATE date, LAST_UPDATED_BY_NE date, DATE_UPDATED_DATABASE date
