FME workspace OSABPlusToSQLServer.fmw
Shutdown Python:
      import subprocess
      subprocess.call([r"D:\Program Files\FME\fme.exe",r"E:\My Learning Folder\FME\Workspace\SpatialIndexCreator.fmw"])

Parameters:
- SourceDataset_GML = E:\My Learning Folder\FME\Data\addressbase-plus-gml-sample-data\sx9090.gml   # Source Geography Markup Language (GML) File(s)
- DestDataset_MSSQL_SPATIAL = OS_SampleData   # SQL Server Connection
- XMIN = @Value($(xmin))   # TYPE:real64 Minimum X Attribute
- XMAX = @Value($(xmax))   # TYPE:real64 Maximum X Attribute
- YMIN = @Value($(ymin))   # TYPE:real64 Minimum Y Attribute
- YMAX = @Value($(ymax))   # TYPE:real64 Maximum Y Attribute

Readers:
- GML_1: GML from $(SourceDataset_GML)

Writers:
- MSSQL_SPATIAL_1: MSSQL_SPATIAL to $(DestDataset_MSSQL_SPATIAL) in OSGB-GPS-2015

Address (reader GML_1)
    attributes: uprn xml_int64, udprn xml_int64, changeType xml_char(1), state xml_char(4), stateDate xml_date, class xml_buffer, parentUPRN xml_int64, position xml_geometry, positionLatLong xml_geometry, rpc xml_char(1), localCustodianCode xml_int64, country xml_buffer, laStartDate xml_date, lastUpdateDate xml_date, entryDate xml_date, rmOrganisationName xml_buffer, rmOrganisationName.xml_lang xml_buffer, laOrganisation xml_buffer, laOrganisation.xml_lang xml_buffer, departmentName xml_buffer, departmentName.xml_lang xml_buffer, legalName xml_buffer, legalName.xml_lang xml_buffer, subBuildingName xml_buffer, subBuildingName.xml_lang xml_buffer, buildingName xml_buffer, buildingName.xml_lang xml_buffer, buildingNumber xml_int64, saoStartNumber xml_int64, saoStartSuffix xml_buffer,
      saoEndNumber xml_int64, saoEndSuffix xml_buffer, saoText xml_buffer, saoText.xml_lang xml_buffer, altLanguageSAOText xml_buffer, altLanguageSAOText.xml_lang xml_buffer, paoStartNumber xml_int64, paoStartSuffix xml_buffer, paoEndNumber xml_int64, paoEndSuffix xml_buffer, paoText xml_buffer, paoText.xml_lang xml_buffer, altLanguagePAOText xml_buffer, altLanguagePAOText.xml_lang xml_buffer, usrn xml_int64, usrnMatchIndicator xml_char(1), areaName xml_buffer, level xml_buffer, officialFlag xml_char(4), osAddressTOID xml_buffer, osAddressTOIDVersion xml_int64, osRoadLinkTOID xml_buffer, osRoadLinkTOIDVersion xml_int64, osTopoTOID xml_buffer, osTopoTOIDVersion xml_int64, voaCTRecord xml_int64, voaNDRRecord xml_int64, streetDescription xml_buffer, streetDescription.xml_lang xml_buffer, altLanguageStreetDescription xml_buffer,
      altLanguageStreetDescription.xml_lang xml_buffer, dependentThoroughfare xml_buffer, dependentThoroughfare.xml_lang xml_buffer, thoroughfare xml_buffer, thoroughfare.xml_lang xml_buffer, welshDependentThoroughfare xml_buffer, welshDependentThoroughfare.xml_lang xml_buffer, welshThoroughfare xml_buffer, welshThoroughfare.xml_lang xml_buffer, doubleDependentLocality xml_buffer, doubleDependentLocality.xml_lang xml_buffer, dependentLocality xml_buffer, dependentLocality.xml_lang xml_buffer, locality xml_buffer, locality.xml_lang xml_buffer, welshDependentLocality xml_buffer, welshDependentLocality.xml_lang xml_buffer, welshDoubleDependentLocality xml_buffer, welshDoubleDependentLocality.xml_lang xml_buffer, townName xml_buffer, townName.xml_lang xml_buffer, administrativeArea xml_buffer, administrativeArea.xml_lang xml_buffer, postTown xml_buffer, postTown.xml_lang xml_buffer, welshPostTown xml_buffer, welshPostTown.xml_lang xml_buffer, postcode xml_buffer, postcodeLocator xml_buffer, postcodeType xml_char(4),
      deliveryPointSuffix xml_buffer, addressbasePostal xml_buffer, poBoxNumber xml_buffer, wardCode xml_buffer, parishCode xml_buffer, rmStartDate xml_date, multiOccCount xml_int64, voaNDRPDescCode xml_buffer, voaNDRScatCode xml_buffer, altLanguage xml_char(4)
    -> CoordinateExtractor
CoordinateExtractor
    Y_ATTR = NORTHING
    Z_ATTR = _z
    IND = 0
    X_ATTR = EASTING
    MODE = Specify Coordinate
    -> Counter
Counter
    START = 1
    SCOPE = Global
    DOMAIN = counter
    CNT_ATTR = OBJECTID
    -> AttributeManager
AttributeManager
    ATTR_TABLE:
      RENAME_SET_VALUE uprn > UPRN
      REMOVE gml_parent_id
      REMOVE gml_parent_property
      REMOVE gml_id
      REMOVE udprn
      RENAME_SET_VALUE class > CLASS
      RENAME_SET_VALUE localCustodianCode > CUSTODIAN_CODE
      REMOVE changeType
      REMOVE state
      REMOVE stateDate
      REMOVE parentUPRN
      REMOVE position
      REMOVE positionLatLong
      REMOVE rpc
      REMOVE country
      REMOVE laStartDate
      REMOVE lastUpdateDate
      RENAME_SET_VALUE departmentName > DEPT_NAME
      RENAME_SET_VALUE legalName > LEGAL_NAME
      REMOVE entryDate
      REMOVE rmOrganisationName
      REMOVE rmOrganisationName.xml_lang
      REMOVE laOrganisation
      REMOVE laOrganisation.xml_lang
      REMOVE departmentName.xml_lang
      REMOVE legalName.xml_lang
      RENAME_SET_VALUE subBuildingName > SUB_BLDG_NAME
      RENAME_SET_VALUE buildingName > BLDG_NAME
      RENAME_SET_VALUE buildingNumber > BLDG_NUMBER
      RENAME_SET_VALUE saoStartNumber > SAO_START_NO
      RENAME_SET_VALUE saoStartSuffix > SAO_START_SFX
      RENAME_SET_VALUE saoEndNumber > SAO_END_NO
      RENAME_SET_VALUE saoEndSuffix > SAO_END_SFX
      RENAME_SET_VALUE saoText > SAO_TEXT
      RENAME_SET_VALUE paoStartNumber > PAO_START_NO
      RENAME_SET_VALUE paoStartSuffix > PAO_START_SFX
      RENAME_SET_VALUE paoEndNumber > PAO_END_NO
      RENAME_SET_VALUE paoEndSuffix > PAO_END_SFX
      RENAME_SET_VALUE paoText > PAO_TEXT
      REMOVE subBuildingName.xml_lang
      REMOVE buildingName.xml_lang
      REMOVE saoText.xml_lang
      REMOVE altLanguageSAOText
      REMOVE altLanguageSAOText.xml_lang
      REMOVE paoText.xml_lang
      REMOVE altLanguagePAOText
      REMOVE altLanguagePAOText.xml_lang
      RENAME_SET_VALUE usrn > USRN
      REMOVE usrnMatchIndicator
      REMOVE areaName
      REMOVE level
      REMOVE officialFlag
      REMOVE osAddressTOID
      REMOVE osAddressTOIDVersion
      REMOVE osRoadLinkTOID
      REMOVE osRoadLinkTOIDVersion
      REMOVE osTopoTOID
      REMOVE osTopoTOIDVersion
      REMOVE voaCTRecord
      REMOVE voaNDRRecord
      RENAME_SET_VALUE streetDescription > STREET_NAME
      RENAME_SET_VALUE postTown > TOWN_NAME
      RENAME_SET_VALUE postcodeLocator > POSTCODE
      REMOVE streetDescription.xml_lang
      SET_TO LATITUDE = @Value(NORTHING)
      SET_TO LONGITUDE = @Value(EASTING)
      SET_TO FULL_ADDRESS
      REMOVE altLanguageStreetDescription
      REMOVE altLanguageStreetDescription.xml_lang
      REMOVE dependentThoroughfare
      REMOVE dependentThoroughfare.xml_lang
      REMOVE thoroughfare
      REMOVE thoroughfare.xml_lang
      REMOVE welshDependentThoroughfare
      REMOVE welshDependentThoroughfare.xml_lang
      REMOVE welshThoroughfare
      REMOVE welshThoroughfare.xml_lang
      REMOVE doubleDependentLocality
      REMOVE doubleDependentLocality.xml_lang
      REMOVE dependentLocality
      REMOVE dependentLocality.xml_lang
      REMOVE locality
      REMOVE locality.xml_lang
      REMOVE welshDependentLocality
      REMOVE welshDependentLocality.xml_lang
      REMOVE welshDoubleDependentLocality
      REMOVE welshDoubleDependentLocality.xml_lang
      REMOVE townName
      REMOVE townName.xml_lang
      REMOVE administrativeArea
      REMOVE administrativeArea.xml_lang
      REMOVE _z
      REMOVE postTown.xml_lang
      REMOVE welshPostTown
      REMOVE welshPostTown.xml_lang
      REMOVE postcode
      REMOVE postcodeType
      REMOVE deliveryPointSuffix
      REMOVE addressbasePostal
      REMOVE poBoxNumber
      REMOVE wardCode
      REMOVE parishCode
      REMOVE rmStartDate
      REMOVE multiOccCount
      REMOVE voaNDRPDescCode
      REMOVE voaNDRScatCode
      REMOVE altLanguage
    -> AttributeReprojector
AttributeReprojector
    SOURCE = OSGB-GPS-2015
    DEST = LL-ETRS89/01
    XATTR = LONGITUDE
    YATTR = LATITUDE
    -> OS_ABPLUS_SAMPLE (writer MSSQL_SPATIAL_1)
OS_ABPLUS_SAMPLE (writer MSSQL_SPATIAL_1)
    attributes: OBJECTID integer,PrimaryKey, UPRN varchar(200), CLASS varchar(200), CUSTODIAN_CODE varchar(200), DEPT_NAME varchar(200), LEGAL_NAME varchar(200), SUB_BLDG_NAME varchar(200), BLDG_NAME varchar(200), BLDG_NUMBER integer, SAO_START_NO integer, SAO_START_SFX varchar(200), SAO_END_NO integer, SAO_END_SFX varchar(200), SAO_TEXT varchar(200), PAO_START_NO integer, PAO_START_SFX varchar(200), PAO_END_NO integer, PAO_END_SFX varchar(200), PAO_TEXT varchar(200), USRN varchar(200), STREET_NAME varchar(200), TOWN_NAME varchar(200), POSTCODE varchar(200), EASTING numeric(10,10), NORTHING numeric(10,10), LATITUDE numeric(20,10), LONGITUDE numeric(20,10), FULL_ADDRESS varchar(200)
